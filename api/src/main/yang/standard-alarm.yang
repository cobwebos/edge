module standard-alarm {
    namespace 'http://www.cobwebos.com/netconf/alarm' ;
    prefix alarm ;
    import ietf-yang-types { prefix yang; }
	import ietf-inet-types { prefix inet; }

    description
    "This module contains all type of alarm for the netconf device.";

    revision 2018-06-01 {
      description
      "alarm add notification";
    }
    revision 2018-05-04 {
      description
      "alarm";
    }

    typedef severity-classification {

        type enumeration {
            enum critical {
                value 1 ;
                description "severity-classification critical";
            }

            enum major {
                value 2 ;
                description "severity-classification major";
            }

            enum minor {
                value 3 ;
                description "severity-classification minor";
            }

            enum warning {
                value 4 ;
                description "severity-classification warning";
            }
 	        enum notification {
                value 5 ;
                description "severity-classification notification";
            }

        }
        description "severity classification";
    } 

    typedef alarm-status {
        type enumeration {
            enum occurred {
                value 1 ;
                description "alarm occurred";
            }

            enum cleared {
                value 2 ;
                description "alarm cleared";
            }
        }
        description "alarm status";
    }

    grouping alarm-report {
        list almCodelist {
            key "alarm-code";
            leaf sequence-no {
                type uint32 {
                    range "1..4294967295";
                }
            }

            leaf alarm-code {
                type string ;
                description "alarm code" ;
            }

			leaf alarm-name {
				type string ;
				description "alarm name" ;
			}
			
            leaf severity {
                type severity-classification ;
                description "severity classification" ;
            }

            leaf timestamp {
                type "yang:timestamp";
                description "the timestamp is the number of seconds since 2000/01/01 00:00:00" ;
            }

            leaf alarm-status {
                type alarm-status ;
                description "alarm status" ;
            }

            leaf alarm-description {
                type string {
                    length "1..255" ;
                }
                description "the alarm description" ;
            }

            leaf alarm-resource{
                type string {
                    length "1..255" ;
                }
                mandatory true;
            }
			
			leaf ipaddr {
				type inet:ip-address;
			}
        }
    }

    notification current-alarm-report {
        uses alarm-report ;
    }// notification
} // module
