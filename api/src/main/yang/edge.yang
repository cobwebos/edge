module edge {
    yang-version 1.1;
    namespace "urn:opendaylight:params:xml:ns:yang:edge";
    prefix "edge";

    revision "2017-08-30" { // TODO change revision to date of model creation
        description "Initial revision of edge model";
    }
    rpc hello {
        output{
        leaf status {
         type string;
        } 
       }
    }
    
}
